SAMRH71-RTEMS-SERIAL-DRIVER DEFINITIONS AUTOMATIC TAGS ::= BEGIN

Serial-SamRH71-Rtems-Device-T    ::= ENUMERATED {
   uart0,
   uart1,
   uart2,
   uart3,
   uart4,
   uart5,
   uart6,
   uart7,
   uart8,
   uart9
}

Serial-SamRH71-Rtems-Baudrate-T  ::= ENUMERATED {b9600, b19200, b38400, b57600, b115200, b230400}

Serial-SamRH71-Rtems-Parity-T    ::= ENUMERATED {even, odd, none}

Serial-SamRH71-Escape-Byte-T ::= INTEGER(0..255)

-- The choice option cannot be NULL or empty SEQUENCE to work with space creator.
Serial-SamRH71-Rtems-Dummy ::= BOOLEAN

Serial-SamRH71-Rtems-Packetizer-Mode-T    ::= CHOICE {
   escaped-packets BOOLEAN,
   raw CHOICE {
      -- Single-byte mode: driver passes the received bytes immediately after reception.
      single-byte         Serial-SamRH71-Rtems-Dummy,
      -- Custom escape mode: Driver passes all the received bytes to user application
      --                     after receiving specified byte.
      custom-escape-byte  Serial-SamRH71-Escape-Byte-T
   }
}

-- Transmission handling mode
Serial-SamRH71-Rtems-Tx-Mode-T ::= ENUMERATED {
   -- Uses DMA, recommended for escaped-packets and large amount of data
   asynchronous,
   -- Synchronously writes bytes, recommended for single-byte mode and small amounts of data
   blocking
}

Serial-SamRH71-Rtems-Conf-T ::= SEQUENCE {
   devname        Serial-SamRH71-Rtems-Device-T,
   speed          Serial-SamRH71-Rtems-Baudrate-T,
   parity         Serial-SamRH71-Rtems-Parity-T,
   packetizer-mode Serial-SamRH71-Rtems-Packetizer-Mode-T,
   tx-mode        Serial-SamRH71-Rtems-Tx-Mode-T
}

END
