SAMRH71-RTEMS-CAN-DRIVER DEFINITIONS AUTOMATIC TAGS ::= BEGIN

    CAN-Samrh71-Rtems-Interface-T ::= ENUMERATED {
        mcan-interface-mcan0,
        mcan-interface-mcan1
    }

    CAN-Samrh71-Rtems-PCK-Clock-Source ::= ENUMERATED {
        pck-clock-source-main-clock,
        pck-clock-source-plla-clock,
        pck-clock-source-pllb-clock,
        pck-clock-source-master-clock,
        pck-clock-source-rc2-clock
    }

    CAN-Samrh71-Rtems-PCK-Prescaler ::= INTEGER (0 .. 255)

    CAN-Samrh71-Rtems-Data-Synchronization-Jump-Width ::= INTEGER (0 .. 7)

    CAN-Samrh71-Rtems-Data-Time-Segment-Before-Sample-Point ::= INTEGER (1 .. 31)

    CAN-Samrh71-Rtems-Data-Time-Segment-After-Sample-Point ::= INTEGER (0 .. 15)

    CAN-Samrh71-Rtems-Data-Bit-Rate-Prescaler ::= INTEGER (0 .. 31)

    CAN-Samrh71-Rtems-Standard-Can-Id ::= INTEGER (0 .. 2047)

    CAN-Samrh71-Rtems-Extended-Can-Id ::= INTEGER (0 .. 536870911)

    -- Elements of CHOICE shall by globally unique in single TASTE project, hence a prefix
    CAN-Samrh71-Rtems-Can-Id ::= CHOICE {
        can-samrh71-can-id-standard CAN-Samrh71-Rtems-Standard-Can-Id,
        can-samrh71-can-id-extended CAN-Samrh71-Rtems-Extended-Can-Id
    }

    -- The choice option cannot be NULL or empty SEQUENCE to work with space creator.
    CAN-Samrh71-Rtems-Dummy ::= BOOLEAN

    -- Elements of CHOICE shall by globally unique in single TASTE project, hence a prefix
    -- This determines what value shall be used for CAN-ID for output frames.
    CAN-Samrh71-Rtems-Address ::= CHOICE {
        -- The first option sets one constant CAN-ID for all output frames.
        can-samrh71-static-can-id CAN-Samrh71-Rtems-Can-Id,
        -- The second option allows the application to specify exact value of CAN-ID.  Driver uses first four
        -- bytes of every message interpreted as uint32_t to determine CAN-ID. The lowest 11 or 29 bits are a
        -- value of CAN-ID, where bit 30 determines if CAN-ID is standard (11 bit) or extended (29 bit).  The
        -- actual data to send in a frame begins from byte 5 of message.
        can-samrh71-application-control-can-id CAN-Samrh71-Rtems-Dummy
    }

    CAN-SamRH71-Rtems-Conf-T ::= SEQUENCE {
        can-interface CAN-Samrh71-Rtems-Interface-T,
        bit-rate-prescaler CAN-Samrh71-Rtems-Data-Bit-Rate-Prescaler DEFAULT 0,
        synchronization-jump CAN-Samrh71-Rtems-Data-Synchronization-Jump-Width DEFAULT 2,
        time-segments-after-sample-point CAN-Samrh71-Rtems-Data-Time-Segment-After-Sample-Point DEFAULT 2,
        time-segments-before-sample-point CAN-Samrh71-Rtems-Data-Time-Segment-Before-Sample-Point DEFAULT 15,

        pck-source CAN-Samrh71-Rtems-PCK-Clock-Source DEFAULT pck-clock-source-plla-clock,
        pck-prescaler CAN-Samrh71-Rtems-PCK-Prescaler DEFAULT 14,
        address CAN-Samrh71-Rtems-Address
    }

END
